FME workspace Conversion_pipeline.fmw

Parameters:
- SourceDataset_SHAPEFILE = $(FME_MF_DIR)Sewerage_Network_Main_Pipelines-shp\85e6e9e4-1bec-48b9-8982-253ed749a2a7202041-1-1obtgd5.s962.shp   # Source Esri Shapefile(s)
- SourceDataset_SQLITE3FDO_5 = $(FME_MF_DIR)Case study 2\1377176\Case study 2.sqlite   # SQLite3 Spatial (FDO) Database
- SourceDataset_SHAPEFILE_7 = D:\Implementation\CityGML\Demonstration\Case study 1\Shapefiles\Parcel\Parcel_properties.shp   # Source Esri Shapefile(s)
- DestDataset_GML_3 = $(FME_MF_DIR)Prototype.gml   # Destination Geography Markup Language (GML) File
- SourceDataset_FBX_7 = $(FME_MF_DIR)3D models\roads.fbx   # Source FBX File(s)
- SourceDataset_FBX = $(FME_MF_DIR)3D models\ground.fbx   # Source FBX File(s)
- SourceDataset_GEODATABASE_FILE_5 = $(FME_MF_DIR)Shapefiles\New File Geodatabase.gdb   # File Geodatabase
- SourceDataset_GEODATABASE_FILE_4 = $(FME_MF_DIR)Shapefiles\New File Geodatabase.gdb   # File Geodatabase
- SourceDataset_GEODATABASE_FILE = $(FME_MF_DIR)Shapefiles\New File Geodatabase.gdb   # File Geodatabase

Readers:
- SHAPEFILE_1: SHAPEFILE from $(SourceDataset_SHAPEFILE)
- SQLITE3FDO_2: SQLITE3FDO from $(SourceDataset_SQLITE3FDO_5)
- SHAPEFILE_3: SHAPEFILE from $(SourceDataset_SHAPEFILE_7)
- FBX_1: FBX from $(SourceDataset_FBX) in MGA94-55
- FBX_3: FBX from $(SourceDataset_FBX_7) in MGA94-55
- GEODATABASE_FILE_2: GEODATABASE_FILE from $(SourceDataset_GEODATABASE_FILE_5)
- GEODATABASE_FILE_1: GEODATABASE_FILE from $(SourceDataset_GEODATABASE_FILE)
- GEODATABASE_FILE_3: GEODATABASE_FILE from $(SourceDataset_GEODATABASE_FILE_4)

Writers:
- GML_2: GML to $(DestDataset_GML_3) in MGA94-55

Offsetter_5
    MODE = Cartesian Coordinate
    XOFF = 0
    YOFF = 0
    ZOFF = 30
    OFFSET -> GeometryExtractor_4
GeometryExtractor_4
    ATTR = elevationLevels
    GENERATE_GEOMETRY_IDS = No
    KIND_LONG = GML v3.2.1
    OMIT_NAMESPACES_DISPLAY = No
    PREFER_POLYGON_OVER_SURFACE = No
    REMOVE_GEOMETRY = No
    -> AttributeCreator_5
AttributeCreator_5
    ATTR_TABLE = SET_TO gml_id = id_@UUID()
    -> FeatureMerger_5 [REQUESTOR]
Offsetter_3
    MODE = Cartesian Coordinate
    XOFF = 0
    YOFF = 0
    ZOFF = @Value(Offsetter_value)
    OFFSET -> GeometryExtractor_5
    OFFSET -> AttributeFilter
GeometryExtractor_5
    ATTR = surveyPoints
    GENERATE_GEOMETRY_IDS = No
    KIND_LONG = GML v3.2.1
    OMIT_NAMESPACES_DISPLAY = No
    PREFER_POLYGON_OVER_SURFACE = No
    REMOVE_GEOMETRY = No
    -> AttributeCreator_3
AttributeCreator_3
    ATTR_TABLE:
      SET_TO gml_id = id_@UUID()
      SET_TO gml_name{0} = @Value(gml_name)
    -> FeatureMerger_3 [REQUESTOR]
AttributeFilter
    ATTR_NAME = gml_name
    ATTR_VALUES = <Empty>,<Missing>,<Null>,<Unfiltered>,PM358,F,T1,T2,T3,T4,T5,T6,1,2,3,4
    PM358 -> LineBuilder
    F -> LineBuilder
    F -> LineBuilder_2
    F -> LineBuilder_8
    T1 -> LineBuilder_2
    T1 -> LineBuilder_3
    T2 -> LineBuilder_3
    T2 -> LineBuilder_4
    T3 -> LineBuilder_4
    T3 -> LineBuilder_5
    T4 -> LineBuilder_5
    T4 -> LineBuilder_6
    T4 -> LineBuilder_11
    T4 -> LineBuilder_12
    T4 -> LineBuilder_13
    T4 -> LineBuilder_14
    T4 -> LineBuilder_15
    T4 -> LineBuilder_16
    T5 -> LineBuilder_6
    T5 -> LineBuilder_7
    T5 -> LineBuilder_9
    T5 -> LineBuilder_10
    T5 -> LineBuilder_17
    T5 -> LineBuilder_18
    T6 -> LineBuilder_7
    T6 -> LineBuilder_8
    1 -> LineBuilder_9
    2 -> LineBuilder_10
    3 -> LineBuilder_11
    4 -> LineBuilder_12
LineBuilder
    ACCUM_INPUT_ATTRS = Drop Incoming Attributes
    REMOVE_DUPLICATES = No
    LINE -> GeometryExtractor_3
LineBuilder_2
    ACCUM_INPUT_ATTRS = Drop Incoming Attributes
    REMOVE_DUPLICATES = No
    LINE -> GeometryExtractor_3
LineBuilder_3
    ACCUM_INPUT_ATTRS = Drop Incoming Attributes
    REMOVE_DUPLICATES = No
    LINE -> GeometryExtractor_3
LineBuilder_4
    ACCUM_INPUT_ATTRS = Drop Incoming Attributes
    REMOVE_DUPLICATES = No
    LINE -> GeometryExtractor_3
LineBuilder_5
    ACCUM_INPUT_ATTRS = Drop Incoming Attributes
    REMOVE_DUPLICATES = No
    LINE -> AttributeCreator_6
AttributeCreator_6
    ATTR_TABLE:
      SET_TO observationType = traverse
      SET_TO startPoint = T3
      SET_TO endPoint = T4
      SET_TO distanceType = measured
      SET_TO distance = 10.37
      SET_TO bearingType = measured
      SET_TO bearing = 282.53
    -> GeometryExtractor_3
LineBuilder_6
    ACCUM_INPUT_ATTRS = Drop Incoming Attributes
    REMOVE_DUPLICATES = No
    LINE -> AttributeCreator_7
AttributeCreator_7
    ATTR_TABLE:
      SET_TO observationType = traverse
      SET_TO startPoint = T4
      SET_TO endPoint = T5
      SET_TO distanceType = measured
      SET_TO distance = 35.10
      SET_TO bearingType = measured
      SET_TO bearing = 9.78
    -> GeometryExtractor_3
LineBuilder_7
    ACCUM_INPUT_ATTRS = Drop Incoming Attributes
    REMOVE_DUPLICATES = No
    LINE -> GeometryExtractor_3
LineBuilder_8
    ACCUM_INPUT_ATTRS = Drop Incoming Attributes
    REMOVE_DUPLICATES = No
    LINE -> GeometryExtractor_3
LineBuilder_9
    ACCUM_INPUT_ATTRS = Drop Incoming Attributes
    REMOVE_DUPLICATES = No
    LINE -> GeometryExtractor_3
LineBuilder_10
    ACCUM_INPUT_ATTRS = Drop Incoming Attributes
    REMOVE_DUPLICATES = No
    LINE -> GeometryExtractor_3
LineBuilder_11
    ACCUM_INPUT_ATTRS = Drop Incoming Attributes
    REMOVE_DUPLICATES = No
    LINE -> GeometryExtractor_3
LineBuilder_12
    ACCUM_INPUT_ATTRS = Drop Incoming Attributes
    REMOVE_DUPLICATES = No
    LINE -> AttributeCreator
AttributeCreator
    ATTR_TABLE:
      SET_TO observationType = radiation
      SET_TO startPoint = T4
      SET_TO endPoint = 4
      SET_TO distanceType = measured
      SET_TO distance = 4.19
      SET_TO bearingType = measured
      SET_TO bearing = 347.1
    -> GeometryExtractor_3
Offsetter_4
    MODE = Cartesian Coordinate
    XOFF = 0
    YOFF = 0
    ZOFF = 29
    OFFSET -> AttributeFilter_3
AttributeFilter_3
    ATTR_NAME = OBJECTID
    ATTR_VALUES = <Empty>,<Missing>,<Null>,<Unfiltered>,1,2,3,4,5,7
    1 -> LineBuilder_13
    2 -> LineBuilder_14
    3 -> LineBuilder_15
    4 -> LineBuilder_16
    5 -> LineBuilder_17
    7 -> LineBuilder_18
LineBuilder_13
    ACCUM_INPUT_ATTRS = Drop Incoming Attributes
    REMOVE_DUPLICATES = No
    LINE -> GeometryExtractor_3
LineBuilder_14
    ACCUM_INPUT_ATTRS = Drop Incoming Attributes
    REMOVE_DUPLICATES = No
    LINE -> GeometryExtractor_3
LineBuilder_15
    ACCUM_INPUT_ATTRS = Drop Incoming Attributes
    REMOVE_DUPLICATES = No
    LINE -> GeometryExtractor_3
LineBuilder_16
    ACCUM_INPUT_ATTRS = Drop Incoming Attributes
    REMOVE_DUPLICATES = No
    LINE -> GeometryExtractor_3
LineBuilder_17
    ACCUM_INPUT_ATTRS = Drop Incoming Attributes
    REMOVE_DUPLICATES = No
    LINE -> GeometryExtractor_3
LineBuilder_18
    ACCUM_INPUT_ATTRS = Drop Incoming Attributes
    REMOVE_DUPLICATES = No
    LINE -> GeometryExtractor_3
GeometryExtractor_3
    ATTR = surveyObservations
    GENERATE_GEOMETRY_IDS = No
    KIND_LONG = GML v3.2.1
    OMIT_NAMESPACES_DISPLAY = No
    PREFER_POLYGON_OVER_SURFACE = No
    REMOVE_GEOMETRY = No
    -> AttributeCreator_4
AttributeCreator_4
    ATTR_TABLE = SET_TO gml_id = id_@UUID()
    -> FeatureMerger_4 [REQUESTOR]
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryExtractor_2
CityModel (writer GML_2)
    attributes: adeOfAbstractFeature{} xml_xml, creationDate xml_datetime, terminationDate xml_datetime, validFrom xml_datetime, validTo xml_datetime, adeOfAbstractFeatureWithLifespan{} xml_xml, engineeringCRS xml_xml, engineeringCRS.nilReason xml_buffer, engineeringCRS.gml_remoteSchema xml_buffer, engineeringCRS.xlink_href xml_buffer, engineeringCRS.xlink_role xml_buffer, engineeringCRS.xlink_title xml_buffer, engineeringCRS.owns xml_boolean, cityObjectMember{}.nilReason xml_buffer, cityObjectMember{}.gml_remoteSchema xml_buffer, cityObjectMember{}.xlink_href xml_buffer, cityObjectMember{}.xlink_role xml_buffer, cityObjectMember{}.xlink_title xml_buffer, cityObjectMember{}.owns xml_boolean, appearanceMember{}.nilReason xml_buffer, appearanceMember{}.gml_remoteSchema xml_buffer, appearanceMember{}.xlink_href xml_buffer, appearanceMember{}.xlink_role xml_buffer, appearanceMember{}.xlink_title xml_buffer, appearanceMember{}.owns xml_boolean, versionMember{}.nilReason xml_buffer, versionMember{}.gml_remoteSchema xml_buffer, versionMember{}.xlink_href xml_buffer, versionMember{}.xlink_role xml_buffer, versionMember{}.xlink_title xml_buffer,
      versionMember{}.owns xml_boolean, versionTransitionMember{}.nilReason xml_buffer, versionTransitionMember{}.gml_remoteSchema xml_buffer, versionTransitionMember{}.xlink_href xml_buffer, versionTransitionMember{}.xlink_role xml_buffer, versionTransitionMember{}.xlink_title xml_buffer, versionTransitionMember{}.owns xml_boolean, featureMember{}.nilReason xml_buffer, featureMember{}.gml_remoteSchema xml_buffer, featureMember{}.xlink_href xml_buffer, featureMember{}.xlink_role xml_buffer, featureMember{}.xlink_title xml_buffer, featureMember{}.owns xml_boolean, adeOfCityModel{} xml_xml
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> FeatureTypeFilter
FeatureTypeFilter
    ATTRIBUTES = ground,roads,Tunnel,<Blank>,<Unfiltered>
    ground -> TINRelief (writer GML_2)
    roads -> Road (writer GML_2)
    Tunnel -> Tunnel (writer GML_2)
TINRelief (writer GML_2)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, adeOfAbstractSpaceBoundary{} xml_xml, lod xml_int64, extent xml_geometry, adeOfAbstractReliefComponent{} xml_xml, tin xml_geometry, adeOfTINRelief{} xml_xml
Road (writer GML_2)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, spaceType xml_char(8), volume{}.QualifiedVolume.volume xml_real64, volume{}.QualifiedVolume.volume.uom xml_buffer, volume{}.QualifiedVolume.typeOfVolume xml_buffer, volume{}.QualifiedVolume.typeOfVolume.codeSpace xml_buffer, area{}.QualifiedArea.area xml_real64, area{}.QualifiedArea.area.uom xml_buffer, area{}.QualifiedArea.typeOfArea xml_buffer, area{}.QualifiedArea.typeOfArea.codeSpace xml_buffer, boundary{}.nilReason xml_buffer, boundary{}.gml_remoteSchema xml_buffer, boundary{}.xlink_href xml_buffer, boundary{}.xlink_role xml_buffer, boundary{}.xlink_title xml_buffer, boundary{}.owns xml_boolean, lod0Point xml_geometry, lod0MultiSurface xml_geometry, lod0MultiCurve xml_geometry, lod1Solid xml_geometry, lod2Solid xml_geometry, lod2MultiSurface xml_geometry, lod2MultiCurve xml_geometry, lod3Solid xml_geometry, lod3MultiSurface xml_geometry, lod3MultiCurve xml_geometry, adeOfAbstractSpace{} xml_xml, lod1TerrainIntersectionCurve xml_geometry, lod2TerrainIntersectionCurve xml_geometry,
      lod3TerrainIntersectionCurve xml_geometry, pointCloud.nilReason xml_buffer, pointCloud.gml_remoteSchema xml_buffer, pointCloud.xlink_href xml_buffer, pointCloud.xlink_role xml_buffer, pointCloud.xlink_title xml_buffer, pointCloud.owns xml_boolean, adeOfAbstractPhysicalSpace{} xml_xml, adeOfAbstractUnoccupiedSpace{} xml_xml, trafficDirection xml_char(9), occupancy{}.Occupancy.numberOfOccupants xml_int64, occupancy{}.Occupancy.interval xml_buffer, occupancy{}.Occupancy.interval.codeSpace xml_buffer, occupancy{}.Occupancy.occupantType xml_buffer, occupancy{}.Occupancy.occupantType.codeSpace xml_buffer, trafficSpace{}.nilReason xml_buffer, trafficSpace{}.gml_remoteSchema xml_buffer, trafficSpace{}.xlink_href xml_buffer, trafficSpace{}.xlink_role xml_buffer, trafficSpace{}.xlink_title xml_buffer, trafficSpace{}.owns xml_boolean, auxiliaryTrafficSpace{}.nilReason xml_buffer, auxiliaryTrafficSpace{}.gml_remoteSchema xml_buffer, auxiliaryTrafficSpace{}.xlink_href xml_buffer, auxiliaryTrafficSpace{}.xlink_role xml_buffer, auxiliaryTrafficSpace{}.xlink_title xml_buffer, auxiliaryTrafficSpace{}.owns xml_boolean, hole{}.nilReason xml_buffer, hole{}.gml_remoteSchema xml_buffer, hole{}.xlink_href xml_buffer,
      hole{}.xlink_role xml_buffer, hole{}.xlink_title xml_buffer, hole{}.owns xml_boolean, marking{}.nilReason xml_buffer, marking{}.gml_remoteSchema xml_buffer, marking{}.xlink_href xml_buffer, marking{}.xlink_role xml_buffer, marking{}.xlink_title xml_buffer, marking{}.owns xml_boolean, adeOfAbstractTransportationSpace{} xml_xml, class xml_buffer, class.codeSpace xml_buffer, function{} xml_buffer, function{}.codeSpace xml_buffer, usage{} xml_buffer, usage{}.codeSpace xml_buffer, section{}.nilReason xml_buffer, section{}.gml_remoteSchema xml_buffer, section{}.xlink_href xml_buffer, section{}.xlink_role xml_buffer, section{}.xlink_title xml_buffer, section{}.owns xml_boolean, intersection{}.nilReason xml_buffer, intersection{}.gml_remoteSchema xml_buffer, intersection{}.xlink_href xml_buffer, intersection{}.xlink_role xml_buffer, intersection{}.xlink_title xml_buffer, intersection{}.owns xml_boolean, adeOfRoad{} xml_xml
Tunnel (writer GML_2)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, spaceType xml_char(8), volume{}.QualifiedVolume.volume xml_real64, volume{}.QualifiedVolume.volume.uom xml_buffer, volume{}.QualifiedVolume.typeOfVolume xml_buffer, volume{}.QualifiedVolume.typeOfVolume.codeSpace xml_buffer, area{}.QualifiedArea.area xml_real64, area{}.QualifiedArea.area.uom xml_buffer, area{}.QualifiedArea.typeOfArea xml_buffer, area{}.QualifiedArea.typeOfArea.codeSpace xml_buffer, boundary{}.nilReason xml_buffer, boundary{}.gml_remoteSchema xml_buffer, boundary{}.xlink_href xml_buffer, boundary{}.xlink_role xml_buffer, boundary{}.xlink_title xml_buffer, boundary{}.owns xml_boolean, lod0Point xml_geometry, lod0MultiSurface xml_geometry, lod0MultiCurve xml_geometry, lod1Solid xml_geometry, lod2Solid xml_geometry, lod2MultiSurface xml_geometry, lod2MultiCurve xml_geometry, lod3Solid xml_geometry, lod3MultiSurface xml_geometry, lod3MultiCurve xml_geometry, adeOfAbstractSpace{} xml_xml, lod1TerrainIntersectionCurve xml_geometry, lod2TerrainIntersectionCurve xml_geometry,
      lod3TerrainIntersectionCurve xml_geometry, pointCloud.nilReason xml_buffer, pointCloud.gml_remoteSchema xml_buffer, pointCloud.xlink_href xml_buffer, pointCloud.xlink_role xml_buffer, pointCloud.xlink_title xml_buffer, pointCloud.owns xml_boolean, adeOfAbstractPhysicalSpace{} xml_xml, lod1ImplicitRepresentation.nilReason xml_buffer, lod1ImplicitRepresentation.gml_remoteSchema xml_buffer, lod1ImplicitRepresentation.xlink_href xml_buffer, lod1ImplicitRepresentation.xlink_role xml_buffer, lod1ImplicitRepresentation.xlink_title xml_buffer, lod1ImplicitRepresentation.owns xml_boolean, lod1ImplicitRepresentation.ImplicitGeometry.gml_id xml_buffer, lod1ImplicitRepresentation.ImplicitGeometry.transformationMatrix xml_buffer, lod1ImplicitRepresentation.ImplicitGeometry.mimeType xml_buffer, lod1ImplicitRepresentation.ImplicitGeometry.mimeType.codeSpace xml_buffer, lod1ImplicitRepresentation.ImplicitGeometry.libraryObject xml_buffer, lod1ImplicitRepresentation.ImplicitGeometry.referencePoint xml_geometry, lod1ImplicitRepresentation.ImplicitGeometry.relativeGeometry xml_geometry, lod1ImplicitRepresentation.ImplicitGeometry.appearance{}.nilReason xml_buffer, lod1ImplicitRepresentation.ImplicitGeometry.appearance{}.gml_remoteSchema xml_buffer, lod1ImplicitRepresentation.ImplicitGeometry.appearance{}.xlink_href xml_buffer, lod1ImplicitRepresentation.ImplicitGeometry.appearance{}.xlink_role xml_buffer, lod1ImplicitRepresentation.ImplicitGeometry.appearance{}.xlink_title xml_buffer, lod1ImplicitRepresentation.ImplicitGeometry.appearance{}.owns xml_boolean, lod2ImplicitRepresentation.nilReason xml_buffer, lod2ImplicitRepresentation.gml_remoteSchema xml_buffer, lod2ImplicitRepresentation.xlink_href xml_buffer,
      lod2ImplicitRepresentation.xlink_role xml_buffer, lod2ImplicitRepresentation.xlink_title xml_buffer, lod2ImplicitRepresentation.owns xml_boolean, lod2ImplicitRepresentation.ImplicitGeometry.gml_id xml_buffer, lod2ImplicitRepresentation.ImplicitGeometry.transformationMatrix xml_buffer, lod2ImplicitRepresentation.ImplicitGeometry.mimeType xml_buffer, lod2ImplicitRepresentation.ImplicitGeometry.mimeType.codeSpace xml_buffer, lod2ImplicitRepresentation.ImplicitGeometry.libraryObject xml_buffer, lod2ImplicitRepresentation.ImplicitGeometry.referencePoint xml_geometry, lod2ImplicitRepresentation.ImplicitGeometry.relativeGeometry xml_geometry, lod2ImplicitRepresentation.ImplicitGeometry.appearance{}.nilReason xml_buffer, lod2ImplicitRepresentation.ImplicitGeometry.appearance{}.gml_remoteSchema xml_buffer, lod2ImplicitRepresentation.ImplicitGeometry.appearance{}.xlink_href xml_buffer, lod2ImplicitRepresentation.ImplicitGeometry.appearance{}.xlink_role xml_buffer, lod2ImplicitRepresentation.ImplicitGeometry.appearance{}.xlink_title xml_buffer, lod2ImplicitRepresentation.ImplicitGeometry.appearance{}.owns xml_boolean, lod3ImplicitRepresentation.nilReason xml_buffer, lod3ImplicitRepresentation.gml_remoteSchema xml_buffer, lod3ImplicitRepresentation.xlink_href xml_buffer, lod3ImplicitRepresentation.xlink_role xml_buffer, lod3ImplicitRepresentation.xlink_title xml_buffer, lod3ImplicitRepresentation.owns xml_boolean, lod3ImplicitRepresentation.ImplicitGeometry.gml_id xml_buffer, lod3ImplicitRepresentation.ImplicitGeometry.transformationMatrix xml_buffer, lod3ImplicitRepresentation.ImplicitGeometry.mimeType xml_buffer, lod3ImplicitRepresentation.ImplicitGeometry.mimeType.codeSpace xml_buffer, lod3ImplicitRepresentation.ImplicitGeometry.libraryObject xml_buffer, lod3ImplicitRepresentation.ImplicitGeometry.referencePoint xml_geometry, lod3ImplicitRepresentation.ImplicitGeometry.relativeGeometry xml_geometry, lod3ImplicitRepresentation.ImplicitGeometry.appearance{}.nilReason xml_buffer,
      lod3ImplicitRepresentation.ImplicitGeometry.appearance{}.gml_remoteSchema xml_buffer, lod3ImplicitRepresentation.ImplicitGeometry.appearance{}.xlink_href xml_buffer, lod3ImplicitRepresentation.ImplicitGeometry.appearance{}.xlink_role xml_buffer, lod3ImplicitRepresentation.ImplicitGeometry.appearance{}.xlink_title xml_buffer, lod3ImplicitRepresentation.ImplicitGeometry.appearance{}.owns xml_boolean, adeOfAbstractOccupiedSpace{} xml_xml, conditionOfConstruction xml_char(17), dateOfConstruction xml_date, dateOfDemolition xml_date, constructionEvent{}.ConstructionEvent.event xml_buffer, constructionEvent{}.ConstructionEvent.event.codeSpace xml_buffer, constructionEvent{}.ConstructionEvent.dateOfEvent xml_date, constructionEvent{}.ConstructionEvent.description xml_buffer, elevation{}.Elevation.elevationReference xml_buffer, elevation{}.Elevation.elevationReference.codeSpace xml_buffer, elevation{}.Elevation.elevationValue xml_buffer, elevation{}.Elevation.elevationValue.srsName xml_buffer, elevation{}.Elevation.elevationValue.srsDimension xml_uint64, elevation{}.Elevation.elevationValue.axisLabels xml_buffer, elevation{}.Elevation.elevationValue.uomLabels xml_buffer, height{}.Height.highReference xml_buffer, height{}.Height.highReference.codeSpace xml_buffer, height{}.Height.lowReference xml_buffer, height{}.Height.lowReference.codeSpace xml_buffer, height{}.Height.status xml_char(9), height{}.Height.value xml_real64, height{}.Height.value.uom xml_buffer, occupancy{}.Occupancy.numberOfOccupants xml_int64, occupancy{}.Occupancy.interval xml_buffer, occupancy{}.Occupancy.interval.codeSpace xml_buffer,
      occupancy{}.Occupancy.occupantType xml_buffer, occupancy{}.Occupancy.occupantType.codeSpace xml_buffer, adeOfAbstractConstruction{} xml_xml, class xml_buffer, class.codeSpace xml_buffer, function{} xml_buffer, function{}.codeSpace xml_buffer, usage{} xml_buffer, usage{}.codeSpace xml_buffer, tunnelConstructiveElement{}.nilReason xml_buffer, tunnelConstructiveElement{}.gml_remoteSchema xml_buffer, tunnelConstructiveElement{}.xlink_href xml_buffer, tunnelConstructiveElement{}.xlink_role xml_buffer, tunnelConstructiveElement{}.xlink_title xml_buffer, tunnelConstructiveElement{}.owns xml_boolean, tunnelInstallation{}.nilReason xml_buffer, tunnelInstallation{}.gml_remoteSchema xml_buffer, tunnelInstallation{}.xlink_href xml_buffer, tunnelInstallation{}.xlink_role xml_buffer, tunnelInstallation{}.xlink_title xml_buffer, tunnelInstallation{}.owns xml_boolean, hollowSpace{}.nilReason xml_buffer, hollowSpace{}.gml_remoteSchema xml_buffer, hollowSpace{}.xlink_href xml_buffer, hollowSpace{}.xlink_role xml_buffer, hollowSpace{}.xlink_title xml_buffer, hollowSpace{}.owns xml_boolean, tunnelFurniture{}.nilReason xml_buffer, tunnelFurniture{}.gml_remoteSchema xml_buffer, tunnelFurniture{}.xlink_href xml_buffer,
      tunnelFurniture{}.xlink_role xml_buffer, tunnelFurniture{}.xlink_title xml_buffer, tunnelFurniture{}.owns xml_boolean, adeOfAbstractTunnel{} xml_xml, tunnelPart{}.nilReason xml_buffer, tunnelPart{}.gml_remoteSchema xml_buffer, tunnelPart{}.xlink_href xml_buffer, tunnelPart{}.xlink_role xml_buffer, tunnelPart{}.xlink_title xml_buffer, tunnelPart{}.owns xml_boolean, adeOfTunnel{} xml_xml
FeatureMerger_11
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> CrownAllotment (writer GML_2)
FeatureMerger_5
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> ElevationSurface (writer GML_2)
FeatureMerger_3
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> SurveyPoint (writer GML_2)
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> LineObservation (writer GML_2)
Address (writer GML_2)
    attributes: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
Appearance (writer GML_2)
    attributes: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
AuxiliaryTrafficArea (writer GML_2)
    attributes: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
AuxiliaryTrafficSpace (writer GML_2)
    attributes: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
BreaklineRelief (writer GML_2)
    attributes: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
Bridge (writer GML_2)
    attributes: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
BridgeConstructiveElement (writer GML_2)
    attributes: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
BridgeFurniture (writer GML_2)
    attributes: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
BridgeInstallation (writer GML_2)
    attributes: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
BridgePart (writer GML_2)
    attributes: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
BridgeRoom (writer GML_2)
    attributes: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
Building (writer GML_2)
    attributes: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
BuildingConstructiveElement (writer GML_2)
    attributes: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
BuildingFurniture (writer GML_2)
    attributes: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
BuildingInstallation (writer GML_2)
    attributes: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
BuildingPart (writer GML_2)
    attributes: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
BuildingRoom (writer GML_2)
    attributes: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
BuildingUnit (writer GML_2)
    attributes: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
CardinalDirectionDoorSurface (writer GML_2)
    attributes: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
CardinalDirectionWallSurface (writer GML_2)
    attributes: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
CeilingSurface (writer GML_2)
    attributes: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
CityFurniture (writer GML_2)
    attributes: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
CityObjectGroup (writer GML_2)
    attributes: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
ClearanceSpace (writer GML_2)
    attributes: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
ClosureSurface (writer GML_2)
    attributes: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
ColumnSurface (writer GML_2)
    attributes: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
CommonProperty (writer GML_2)
    attributes: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
CompositeTimeseries (writer GML_2)
    attributes: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
CrownPortion (writer GML_2)
    attributes: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
DepthLimitation (writer GML_2)
    attributes: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
Door (writer GML_2)
    attributes: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
DoorSurface (writer GML_2)
    attributes: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
Dynamizer (writer GML_2)
    attributes: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
Easement (writer GML_2)
    attributes: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
FloorSurface (writer GML_2)
    attributes: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
GenericLogicalSpace (writer GML_2)
    attributes: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
GenericOccupiedSpace (writer GML_2)
    attributes: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
GenericThematicSurface (writer GML_2)
    attributes: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
GenericTimeseries (writer GML_2)
    attributes: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
GenericUnoccupiedSpace (writer GML_2)
    attributes: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
GeoreferencedTexture (writer GML_2)
    attributes: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
GroundSurface (writer GML_2)
    attributes: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
Hole (writer GML_2)
    attributes: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
HoleSurface (writer GML_2)
    attributes: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
HollowSpace (writer GML_2)
    attributes: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
InteriorDoorSurface (writer GML_2)
    attributes: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
InteriorWallSurface (writer GML_2)
    attributes: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
Intersection (writer GML_2)
    attributes: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
LandUse (writer GML_2)
    attributes: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
Lot (writer GML_2)
    attributes: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
Marking (writer GML_2)
    attributes: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
MassPointRelief (writer GML_2)
    attributes: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
MedianCeilingSurface (writer GML_2)
    attributes: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
MedianDoorSurface (writer GML_2)
    attributes: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
MedianFloorSurface (writer GML_2)
    attributes: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
MedianWallSurface (writer GML_2)
    attributes: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
OtherConstruction (writer GML_2)
    attributes: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
OuterCeilingSurface (writer GML_2)
    attributes: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
OuterFloorSurface (writer GML_2)
    attributes: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
ParameterizedTexture (writer GML_2)
    attributes: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
PlantCover (writer GML_2)
    attributes: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
PointCloud (writer GML_2)
    attributes: adeOfAbstractFeature{} xml_xml, adeOfAbstractPointCloud{} xml_xml, mimeType xml_buffer, mimeType.codeSpace xml_buffer, pointFile xml_buffer, pointFileSrsName xml_buffer, points xml_geometry, adeOfPointCloud{} xml_xml
Railway (writer GML_2)
    attributes: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
RasterRelief (writer GML_2)
    attributes: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
ReliefFeature (writer GML_2)
    attributes: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
Restriction (writer GML_2)
    attributes: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
Reserve (writer GML_2)
    attributes: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
RoofSurface (writer GML_2)
    attributes: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
Section (writer GML_2)
    attributes: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
SolitaryVegetationObject (writer GML_2)
    attributes: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
Square (writer GML_2)
    attributes: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
StageLot (writer GML_2)
    attributes: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
StandardFileTimeseries (writer GML_2)
    attributes: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
Storey (writer GML_2)
    attributes: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
SurveyedSurface (writer GML_2)
    attributes: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
TabulatedFileTimeseries (writer GML_2)
    attributes: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
Track (writer GML_2)
    attributes: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
TrafficArea (writer GML_2)
    attributes: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
TrafficSpace (writer GML_2)
    attributes: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
TunnelConstructiveElement (writer GML_2)
    attributes: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
TunnelFurniture (writer GML_2)
    attributes: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
TunnelInstallation (writer GML_2)
    attributes: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
TunnelPart (writer GML_2)
    attributes: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
Version (writer GML_2)
    attributes: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
VersionTransition (writer GML_2)
    attributes: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
WallSurface (writer GML_2)
    attributes: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
WaterBody (writer GML_2)
    attributes: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
WaterGroundSurface (writer GML_2)
    attributes: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
WaterSurface (writer GML_2)
    attributes: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
Waterway (writer GML_2)
    attributes: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
Window (writer GML_2)
    attributes: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
WindowSurface (writer GML_2)
    attributes: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
X3DMaterial (writer GML_2)
    attributes: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

Bookmark: Reading survey data
ElevationSurfaces (reader GEODATABASE_FILE_3)
    attributes: OBJECTID integer, SHAPE_Length double, SHAPE_Area double, reducedLevel double, verticalDatum char(50)
    -> Offsetter_5
SurveyPoints (reader GEODATABASE_FILE_3)
    attributes: OBJECTID integer, pointType char(255), pointState char(255), monumentType char(255), easting double, northing double, reducedLevel double, horizontalDatum char(255), verticalDatum char(255), gml_description char(255), gml_name char(255), Offsetter_value double
    -> Offsetter_3
TunnelPoints (reader GEODATABASE_FILE_3)
    attributes: OBJECTID integer
    -> Offsetter_4

Bookmark: Reading physical data
ground (reader FBX_1)
    -> GeometryExtractor_1
roads (reader FBX_3)
    -> Deaggregator_2
Tunnel (reader GEODATABASE_FILE_2)
    attributes: OBJECTID integer, PARCEL_PFI char(10), PARCEL_SPI char(18), PC_SPIC integer, PC_DTYPE char(2), PC_LGAC char(3), PC_PLANNO char(9), PC_LOTNO char(12), PARC_ACCLT char(1), PC_ALL char(10), PARCEL_SEC char(12), PC_BLK char(12), PC_PORT char(12), PC_SUB char(12), PC_CRSTAT char(1), PC_PARC char(4), PC_TOWNC char(5), PC_PNUM char(10), PC_FDESC char(80), PC_PART char(1), PC_CREFNO char(15), PC_STAT char(1), PC_PFI_CR date, PARCEL_UFI integer, PC_UFI_CR date, PC_UFI_OL integer, PARV_PFI char(10), PV_CNT_PFI char(10), ZLEVEL char(2), PV_PFI_CR date,
      PARV_UFI integer, PV_UFI_CR date, PV_UFI_OLD integer, Shape_Leng double, Shape_Length double, Shape_Area double
    -> Extruder_1

Bookmark: Defining Geometry and LOD for the integrated model
GeometryExtractor_1
    ATTR = extent
    GENERATE_GEOMETRY_IDS = No
    KIND_LONG = GML v3.2.1
    OMIT_NAMESPACES_DISPLAY = No
    PREFER_POLYGON_OVER_SURFACE = No
    REMOVE_GEOMETRY = No
    -> AttributeCreator_2
GeometryExtractor_2
    ATTR = lod3MultiSurface
    GENERATE_GEOMETRY_IDS = No
    KIND_LONG = GML v3.2.1
    OMIT_NAMESPACES_DISPLAY = No
    PREFER_POLYGON_OVER_SURFACE = No
    REMOVE_GEOMETRY = No
    -> AttributeCreator_2
AttributeCreator_2
    ATTR_TABLE = SET_TO gml_id = id_@UUID()
    -> FeatureMerger_2 [REQUESTOR]

Bookmark: Tunnel
Extruder_1
    DIRECTION = Auto
    DISTANCE = 1.9
    EXTRUDED -> Offsetter_1
Offsetter_1
    MODE = Cartesian Coordinate
    XOFF = 0
    YOFF = 0
    ZOFF = 29
    OFFSET -> GeometryCoercer_2
GeometryCoercer_2
    GQUERY:
      for $geom in //geometry
      where $geom/count(parent::geometry) = 0
      return number($geom/@fme_id)
    KIND = fme_composite_surface
    COERCED -> Deaggregator_3
Deaggregator_3
    EXPLODE_INSTANCES = No
    GEOM_NAME_FIELD = _geometry_name
    LIST_ATTR_MODE_LOOKUP = LEAN
    MODE = Flatten All Levels
    SPLIT_COMPOSITES = Yes
    DEAGGREGATED -> Counter
Counter
    CNT_ATTR = _count
    DOMAIN = counter
    SCOPE = Global
    START = 0
    -> AttributeFilter_2
AttributeFilter_2
    ATTR_NAME = _count
    ATTR_VALUES = <Empty>,<Missing>,<Null>,<Unfiltered>,1,3
    <UNFILTERED> -> Aggregator_2
Aggregator_2
    ACCUM_ATTRS_NAME = Use Attributes From One Feature
    AGGREGATE_TYPE = Homogeneous Collection (If Possible)
    MODE = Geometry - Assemble One Level
    SEP = ,
    AGGREGATE -> GeometryExtractor_2

Bookmark: Reading legal data
UndergroundParcel (reader GEODATABASE_FILE_1)
    attributes: OBJECTID integer, PARCEL_PFI char(10), PARCEL_SPI char(18), PC_SPIC integer, PC_DTYPE char(2), PC_LGAC char(3), PC_PLANNO char(9), PC_LOTNO char(12), PARC_ACCLT char(1), PC_ALL char(10), PARCEL_SEC char(12), PC_BLK char(12), PC_PORT char(12), PC_SUB char(12), PC_CRSTAT char(1), PC_PARC char(4), PC_TOWNC char(5), PC_PNUM char(10), PC_FDESC char(80), PC_PART char(1), PC_CREFNO char(15), PC_STAT char(1), PC_PFI_CR date, PARCEL_UFI integer, PC_UFI_CR date, PC_UFI_OL integer, PARV_PFI char(10), PV_CNT_PFI char(10), ZLEVEL char(2), PV_PFI_CR date,
      PARV_UFI integer, PV_UFI_CR date, PV_UFI_OLD integer, Shape_Leng double, Shape_Length double, Shape_Area double
    -> Extruder_2

Bookmark: New Bookmark
Extruder_2
    DIRECTION = Auto
    DISTANCE = 3.9
    EXTRUDED -> Offsetter_2
Offsetter_2
    MODE = Cartesian Coordinate
    XOFF = 0
    YOFF = 0
    ZOFF = 28
    OFFSET -> AttributeCreator_20
AttributeCreator_20
    ATTR_TABLE:
      SET_TO gml_parent_id = id_@UUID()
      SET_TO parcelDimension = 3D
      SET_TO parcelName = 2009\OP123049
      SET_TO parcelState = extinguished
      SET_TO parcelType = single
      SET_TO parcelUse = tunnel
    -> GeometryRemover_3
    -> AttributeKeeper_7
GeometryRemover_3
    -> FeatureMerger_13 [REQUESTOR]
AttributeKeeper_7
    CREATE_BULK_MODE_FEATURES = NO
    KEEP_ATTRS = gml_parent_id
    -> GeometryCoercer
GeometryCoercer
    GQUERY:
      for $geom in //geometry
      where $geom/count(parent::geometry) = 0
      return number($geom/@fme_id)
    KIND = fme_composite_surface
    COERCED -> Deaggregator
Deaggregator
    EXPLODE_INSTANCES = No
    GEOM_NAME_FIELD = _geometry_name
    LIST_ATTR_MODE_LOOKUP = LEAN
    MODE = Flatten All Levels
    SPLIT_COMPOSITES = Yes
    DEAGGREGATED -> AttributeCreator_19
AttributeCreator_19
    ATTR_TABLE = SET_TO gml_id = id_@UUID()
    -> GeometryExtractor_8
GeometryExtractor_8
    ATTR = lod3MultiSurface
    GENERATE_GEOMETRY_IDS = Yes
    KIND_LONG = GML v3.2.1
    OMIT_NAMESPACES_DISPLAY = No
    PREFER_POLYGON_OVER_SURFACE = No
    REMOVE_GEOMETRY = No
    -> SubstringExtractor
    -> ProjectedSurface (writer GML_2)
SubstringExtractor
    END = 104
    RESULT_ATTR = surface_id
    SRC_STRING = @Value(lod3MultiSurface)
    START = 64
    -> GeometryRemover_2
GeometryRemover_2
    -> AttributeKeeper_6
AttributeKeeper_6
    CREATE_BULK_MODE_FEATURES = NO
    KEEP_ATTRS = surface_id,gml_parent_id
    -> Aggregator
Aggregator
    ACCUM_ATTRS_NAME = Use Attributes From One Feature
    GROUP_BY = gml_parent_id
    LIST_ATTRS_TO_INCLUDE = surface_id
    LIST_NAME = list_surface_id
    MODE = Attributes Only
    SEP = ,
    AGGREGATE -> ListElementCounter
ListElementCounter
    CNT_ATTR = surfaceNum
    LIST_NAME = list_surface_id{}
    -> PythonCaller
PythonCaller
    NEW_ATTRIBUTES = lod3Solid
    PYTHONSOURCE:
      import fmeobjects
      import time

      class XLink(object):

          def __init__(self):
                  pass

          def input(self, feature):

                  link = '<gml:Solid><gml:exterior><gml:Shell>'

                  for x in range(0,feature.getAttribute('surfaceNum')):

                      link = link + '<gml:surfaceMember xlink:href="#' + feature.getAttribute('list_surface_id{%d}.surface_id' %x) + '"/>'

                  link = link + '</gml:Shell></gml:exterior></gml:Solid>'

                  feature.setAttribute("lod3Solid", link)
                  self.pyoutput(feature)

          def close(self):
                  pass
    PYTHONSYMBOL = XLink
    -> FeatureMerger_13 [SUPPLIER]
FeatureMerger_13
    ATTR_ACCUM_MODE = Merge Supplier
    ATTR_CONFLICT_RES = Use Requestor
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    MERGED -> AttributeRenamer_6
AttributeRenamer_6
    ATTR_TABLE = RENAME_SET_DEFAULT gml_parent_id > gml_id
    MISSING_INPUT_ATTRS = PRESERVE
    -> FeatureMerger_11 [REQUESTOR]

Bookmark: Legal spaces from the VicULA ADE
ProjectedSurface (writer GML_2)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, adeOfAbstractSpaceBoundary{} xml_xml, area{}.QualifiedArea.area xml_real64, area{}.QualifiedArea.area.uom xml_buffer, area{}.QualifiedArea.typeOfArea xml_buffer, area{}.QualifiedArea.typeOfArea.codeSpace xml_buffer, lod0MultiCurve xml_geometry, lod0MultiSurface xml_geometry, lod1MultiSurface xml_geometry, lod2MultiSurface xml_geometry, lod3MultiSurface xml_geometry, pointCloud.nilReason xml_buffer, pointCloud.gml_remoteSchema xml_buffer, pointCloud.xlink_href xml_buffer, pointCloud.xlink_role xml_buffer, pointCloud.xlink_title xml_buffer, pointCloud.owns xml_boolean, adeOfAbstractThematicSurface{} xml_xml
CrownAllotment (writer GML_2)
    attributes: adeOfAbstractFeature{} xml_xml, creationDate xml_datetime, terminationDate xml_datetime, validFrom xml_datetime, validTo xml_datetime, adeOfAbstractFeatureWithLifespan{} xml_xml, externalReference{}.ExternalReference.targetResource xml_buffer, externalReference{}.ExternalReference.informationSystem xml_buffer, externalReference{}.ExternalReference.relationType xml_buffer, generalizesTo{}.owns xml_boolean, generalizesTo{}.nilReason xml_buffer, generalizesTo{}.gml_remoteSchema xml_buffer, generalizesTo{}.xlink_href xml_buffer, generalizesTo{}.xlink_role xml_buffer, generalizesTo{}.xlink_title xml_buffer, relativeToTerrain xml_char(33), relativeToWater xml_char(38), relatedTo{}.owns xml_boolean, relatedTo{}.CityObjectRelation.gml_id xml_buffer, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml,
      relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, relatedTo{}.CityObjectRelation.relatedTo.owns xml_boolean, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_role xml_buffer, relatedTo{}.CityObjectRelation.relatedTo.xlink_title xml_buffer, appearance{}.nilReason xml_buffer, appearance{}.gml_remoteSchema xml_buffer, appearance{}.xlink_href xml_buffer, appearance{}.xlink_role xml_buffer, appearance{}.xlink_title xml_buffer, appearance{}.owns xml_boolean, genericAttribute{}.CodeAttribute.name xml_buffer,
      genericAttribute{}.CodeAttribute.value xml_buffer, genericAttribute{}.CodeAttribute.value.codeSpace xml_buffer, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.CodeAttribute xml_xml, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.xlink_role xml_buffer, dynamizer{}.xlink_title xml_buffer,
      dynamizer{}.owns xml_boolean, adeOfAbstractCityObject{} xml_xml, spaceType xml_char(8), volume{}.QualifiedVolume.volume xml_real64, volume{}.QualifiedVolume.volume.uom xml_buffer, volume{}.QualifiedVolume.typeOfVolume xml_buffer, volume{}.QualifiedVolume.typeOfVolume.codeSpace xml_buffer, area{}.QualifiedArea.area xml_real64, area{}.QualifiedArea.area.uom xml_buffer, area{}.QualifiedArea.typeOfArea xml_buffer, area{}.QualifiedArea.typeOfArea.codeSpace xml_buffer, boundary{}.nilReason xml_buffer, boundary{}.gml_remoteSchema xml_buffer, boundary{}.xlink_href xml_buffer, boundary{}.xlink_role xml_buffer, boundary{}.xlink_title xml_buffer, boundary{}.owns xml_boolean, lod0Point xml_geometry, lod0MultiSurface xml_geometry, lod0MultiCurve xml_geometry, lod1Solid xml_geometry, lod2Solid xml_geometry, lod2MultiSurface xml_geometry, lod2MultiCurve xml_geometry, lod3Solid xml_geometry, lod3MultiSurface xml_geometry, lod3MultiCurve xml_geometry, adeOfAbstractSpace{} xml_xml, adeOfAbstractLogicalSpace{} xml_xml, class xml_buffer,
      class.codeSpace xml_buffer, function{} xml_buffer, function{}.codeSpace xml_buffer, usage{} xml_buffer, usage{}.codeSpace xml_buffer, groupMember{}.owns xml_boolean, groupMember{}.Role.gml_id xml_buffer, groupMember{}.Role.role xml_buffer, groupMember{}.Role.groupMember.nilReason xml_buffer, groupMember{}.Role.groupMember.gml_remoteSchema xml_buffer, groupMember{}.Role.groupMember.xlink_href xml_buffer, groupMember{}.Role.groupMember.xlink_role xml_buffer, groupMember{}.Role.groupMember.xlink_title xml_buffer, groupMember{}.Role.groupMember.owns xml_boolean, parent.owns xml_boolean, parent.nilReason xml_buffer, parent.gml_remoteSchema xml_buffer, parent.xlink_href xml_buffer, parent.xlink_role xml_buffer, parent.xlink_title xml_buffer, adeOfCityObjectGroup{} xml_xml, parcelType xml_char(9), parcelState xml_char(12), parcelDimension xml_char(2), parcelUse xml_buffer, parcelTitleType xml_char(17), parcelName xml_buffer, affectedBy{}.nilReason xml_buffer, affectedBy{}.gml_remoteSchema xml_buffer, affectedBy{}.xlink_href xml_buffer,
      affectedBy{}.xlink_role xml_buffer, affectedBy{}.xlink_title xml_buffer, affectedBy{}.owns xml_boolean

Bookmark: Creating a city model
Creator
    GEOMTYPE = Geometry Object
    NUM = 1
    CREATED -> AttributeCreator_1
AttributeCreator_1
    ATTR_TABLE = SET_TO gml_id = id_@UUID()
    -> AttributeRenamer
    -> CityModel (writer GML_2)
AttributeRenamer
    ATTR_TABLE = RENAME_SET_DEFAULT gml_id > gml_parent_id
    MISSING_INPUT_ATTRS = REMOVE
    -> FeatureMerger_2 [SUPPLIER]
    -> FeatureMerger_11 [SUPPLIER]
    -> FeatureMerger_3 [SUPPLIER]
    -> FeatureMerger_4 [SUPPLIER]
    -> FeatureMerger_5 [SUPPLIER]

Bookmark: SurveyElements
ElevationSurface (writer GML_2)
    attributes: gml_metaDataProperty{}.about xml_buffer, gml_metaDataProperty{}.nilReason xml_buffer, gml_metaDataProperty{}.gml_remoteSchema xml_buffer, gml_metaDataProperty{}.xlink_href xml_buffer, gml_metaDataProperty{}.xlink_role xml_buffer, gml_metaDataProperty{}.xlink_title xml_buffer, gml_metaDataProperty{}.gml_GenericMetaData xml_xml, gml_metaDataProperty{}.gml_GenericMetaData.gml_id xml_buffer, gml_description xml_buffer, gml_description.nilReason xml_buffer, gml_description.gml_remoteSchema xml_buffer, gml_description.xlink_href xml_buffer, gml_description.xlink_role xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_role xml_buffer, gml_descriptionReference.xlink_title xml_buffer, gml_identifier xml_buffer, gml_identifier.codeSpace xml_buffer, gml_name{} xml_buffer, gml_name{}.codeSpace xml_buffer, gml_boundedBy xml_geometry, gml_priorityLocation xml_geometry, gml_location xml_geometry, adeOfAbstractFeature{} xml_xml, reducedLevel xml_real64, verticalDatum xml_buffer,
      elevationLevels xml_geometry
SurveyPoint (writer GML_2)
    attributes: gml_metaDataProperty{}.about xml_buffer, gml_metaDataProperty{}.nilReason xml_buffer, gml_metaDataProperty{}.gml_remoteSchema xml_buffer, gml_metaDataProperty{}.xlink_href xml_buffer, gml_metaDataProperty{}.xlink_role xml_buffer, gml_metaDataProperty{}.xlink_title xml_buffer, gml_metaDataProperty{}.gml_GenericMetaData xml_xml, gml_metaDataProperty{}.gml_GenericMetaData.gml_id xml_buffer, gml_description xml_buffer, gml_description.nilReason xml_buffer, gml_description.gml_remoteSchema xml_buffer, gml_description.xlink_href xml_buffer, gml_description.xlink_role xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_role xml_buffer, gml_descriptionReference.xlink_title xml_buffer, gml_identifier xml_buffer, gml_identifier.codeSpace xml_buffer, gml_name{} xml_buffer, gml_name{}.codeSpace xml_buffer, gml_boundedBy xml_geometry, gml_priorityLocation xml_geometry, gml_location xml_geometry, adeOfAbstractFeature{} xml_xml, pointType xml_char(22), pointState xml_char(9),
      monumentType xml_buffer, easting xml_real64, northing xml_real64, reducedLevel xml_real64, horizontalDatum xml_buffer, verticalDatum xml_buffer, surveyPoints xml_geometry
LineObservation (writer GML_2)
    attributes: gml_metaDataProperty{}.about xml_buffer, gml_metaDataProperty{}.nilReason xml_buffer, gml_metaDataProperty{}.gml_remoteSchema xml_buffer, gml_metaDataProperty{}.xlink_href xml_buffer, gml_metaDataProperty{}.xlink_role xml_buffer, gml_metaDataProperty{}.xlink_title xml_buffer, gml_metaDataProperty{}.gml_GenericMetaData xml_xml, gml_metaDataProperty{}.gml_GenericMetaData.gml_id xml_buffer, gml_description xml_buffer, gml_description.nilReason xml_buffer, gml_description.gml_remoteSchema xml_buffer, gml_description.xlink_href xml_buffer, gml_description.xlink_role xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_role xml_buffer, gml_descriptionReference.xlink_title xml_buffer, gml_identifier xml_buffer, gml_identifier.codeSpace xml_buffer, gml_name{} xml_buffer, gml_name{}.codeSpace xml_buffer, gml_boundedBy xml_geometry, gml_priorityLocation xml_geometry, gml_location xml_geometry, adeOfAbstractFeature{} xml_xml, observationType xml_char(10), startPoint xml_buffer,
      endPoint xml_buffer, surveyObservations xml_geometry, relatedPoint{}.nilReason xml_buffer, relatedPoint{}.gml_remoteSchema xml_buffer, relatedPoint{}.xlink_href xml_buffer, relatedPoint{}.xlink_role xml_buffer, relatedPoint{}.xlink_title xml_buffer, relatedPoint{}.owns xml_boolean, distanceType xml_char(15), distance xml_real64, bearingType xml_char(15), bearing xml_real64
ArcObservation (writer GML_2)
    attributes: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
